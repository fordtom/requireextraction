# Subset026

# Specification: Specification Document
- Description: Subset026

## 1
System Requirements Specification Chapter 1 Introduction
- kind: Heading
- Legal Obligation: unknown
- WordTraceId: 16
- atomic: true
- implement: false

### 1.1
Modification History
- kind: ordinary
- Legal Obligation: not applicable
- WordTraceId: 136
- atomic: false
- implement: true

### 1.1[2]
- kind: Placeholder
- Legal Obligation: not applicable
- WordTraceId: 157
- atomic: false
- implement: false

#### 1.1[2].[t]*
| Issue Number Date | Section Number | Modification / Description | Author / Editor |
| --- | --- | --- | --- |
| 0.0.1 | All | first issue | SAB |
| 0.1.0 | All | Review comments from Adtranz | SAB |
| 1.0.0 | All | Final review | SAB |
| 1.0.2 / 15. Apr. 1999 | All | Reworked edition | SAB |
| 1.0.3 / 22. Apr. 1999 | 1.8.9 | Comment of Alstom | SAB |
| 1.1.0 / 23. Apr. 1999 |  | Final issue of class P SRS | Ch. Frerichs (ed.) |
| 1.1.1 / 27. Mai 1999 | 1.3.1.1/1.7.1.2 | Review comments added | SAB |
| 1.1.2 |  | Draft for class 1 | SAB |
| 1.1.3 990729 | Document reference number. | Revision during finalisation meeting, Stuttgart 990729 | HE |
| 1.2.0 990730 | Version number | Release version | HE |
| 1.2.1 991209 | All | First draft for 2 nd release | SAB |
| 1.3.0 991216 | All | Review comments added | SAB |
| 2.0.0 991222 | Minor editing | Finalisation | SAB |
| 2.0.1 | All | Corrections after review | SAB |
| 2.1.0 | Version number | UNISIG release | SAB |
| 2.2.0 | Version number | UNISIG release | SAB |
| 2.2.2 1.2.2002 | Version number | Final edition | Ch. Frerichs |
| 2.3.0 24/02/06 | Version number, no change since 2.2.2 | Release version | HK |
| 3.0.0 23/12/08 | 1.8.7 | Release version Re-use of chapter 6, now dedicated to management of older system versions | AH |
| 3.0.1 22/12/09 |  | Including the results of the editorial review of the SRS 3.0.0 | AH |
| 3.1.0 22/02/10 | No change | Release version | AH |
| 3.2.0 22/12/10 | No change | Release version | AH |
| 3.2.1 13/12/11 |  | Including all CR’s that are in state “Analysis completed” according to ERA CCM. | AH |
| 3.3.0 07/03/12 |  | Baseline 3 release version | AH |
- kind: Table
- Legal Obligation: not applicable
- WordTraceId: 1574
- atomic: false
- implement: false

### 1.2
Table of Contents
- kind: ordinary
- Legal Obligation: not applicable
- WordTraceId: 1575
- atomic: false
- implement: true

### 1.3
Introduction
- kind: Heading
- Legal Obligation: not applicable
- WordTraceId: 2647
- atomic: false
- implement: false

#### 1.3.1
PLACEHOLDER REQUIREMENT - DO NOT TRACE
- kind: Placeholder
- Legal Obligation: not applicable
- WordTraceId: 2660
- atomic: false
- implement: false

##### 1.3.1.1
Train control is an important part of any railway operations management system. In the past a number of different Automatic Train Control (ATC) systems have evolved in different countries at different times. These systems are incompatible and not interoperable with each other. Only a few of these systems are used in more than one country, and even in those cases there have been differences in detailed development which have resulted in incompatible and not interoperable versions.
- kind: ordinary
- Legal Obligation: unknown
- WordTraceId: 2660
- atomic: false
- implement: true

##### 1.3.1.2
Many railways anticipate a significant increase in density of train traffic and are rethinking their infrastructure strategy, to accommodate high levels of traffic, in which ATC systems play an important part. Also many railways would like to introduce standardised systems to reduce system costs. In order to establish international standardisation of ATC systems, the following document specifies the European Rail Traffic Management System/European Train Control System (ERTMS/ETCS).
- kind: ordinary
- implementerEnhanced: Many railways anticipate a
  significant
  [WEAK]
  increase in density of train traffic and are rethinking their infrastructure strategy, to accommodate high levels of traffic, in which ATC systems play an important part. Also many railways would like to introduce standardised systems to reduce system costs. In order to establish international standardisation of ATC systems, the following document specifies the European Rail Traffic Management System/European Train Control System (ERTMS/ETCS).
- Legal Obligation: unknown
- WordTraceId: 3145
- atomic: false
- implement: true

### 1.4
Advantages of an International Interoperable System
- kind: Heading
- Legal Obligation: not applicable
- WordTraceId: 3632
- atomic: false
- implement: false

#### 1.4.1
PLACEHOLDER REQUIREMENT - DO NOT TRACE
- kind: Placeholder
- Legal Obligation: not applicable
- WordTraceId: 3684
- atomic: false
- implement: false

##### 1.4.1.1
The advantages expected by the railways can be summarised as:
- kind: Heading
- Legal Obligation: unknown
- WordTraceId: 3684
- atomic: true
- implement: false

###### 1.4.1.1.*[1]
Cross border interoperability.
- kind: ordinary
- ListNumberText: ·
- Legal Obligation: unknown
- WordTraceId: 3746
- atomic: true
- implement: true

###### 1.4.1.1.*[2]
Improvement of the safety of national and international train traffic.
- kind: ordinary
- ListNumberText: ·
- Legal Obligation: unknown
- WordTraceId: 3777
- atomic: true
- implement: true

###### 1.4.1.1.*[3]
Improvement of international passengers and freight train traffic management.
- kind: ordinary
- ListNumberText: ·
- Legal Obligation: unknown
- WordTraceId: 3848
- atomic: true
- implement: true

###### 1.4.1.1.*[4]
Shorter headway on heavily trafficked lines, by driving on moving block, enabling exploitation of maximum track capacity.
- kind: ordinary
- ListNumberText: ·
- Legal Obligation: unknown
- WordTraceId: 3927
- atomic: true
- implement: true

###### 1.4.1.1.*[5]
The possibility of step-by-step introduction of the new technology.
- kind: ordinary
- ListNumberText: ·
- Legal Obligation: unknown
- WordTraceId: 4049
- atomic: true
- implement: true

###### 1.4.1.1.*[6]
Enabling Pan-European competition between the manufacturers of ERTMS/ETCS components. Strengthening the position of the European railway industry on the world market.
- kind: ordinary
- ListNumberText: ·
- Legal Obligation: unknown
- WordTraceId: 4117
- atomic: false
- implement: true

###### 1.4.1.1.*[7]
Enabling preconditions for future harmonisation in other areas of rail traffic management.
- kind: ordinary
- ListNumberText: ·
- Legal Obligation: unknown
- WordTraceId: 4284
- atomic: true
- implement: true

### 1.5
About this Document
- kind: Heading
- Legal Obligation: not applicable
- WordTraceId: 4375
- atomic: false
- implement: false

#### 1.5.1
PLACEHOLDER REQUIREMENT - DO NOT TRACE
- kind: Placeholder
- Legal Obligation: not applicable
- WordTraceId: 4395
- atomic: false
- implement: false

##### 1.5.1.1
The purpose of this document is to specify the unified European Train Control System (ETCS) from a technical point of view.
- kind: ordinary
- Legal Obligation: unknown
- WordTraceId: 4395
- atomic: true
- implement: true

##### 1.5.1.2
Some parts of the system are only specified to allow a migration from existing train control systems to ETCS (e.g. STM’s) over a transition period. They might be removed in a future edition of the standard.
- kind: ordinary
- implementerEnhanced: Some parts of the system are only specified to allow a migration from existing train control systems to ETCS (
  e.g.
  [WEAK]
  STM’s) over a transition period. They might be removed in a future edition of the standard.
- Legal Obligation: unknown
- WordTraceId: 4519
- atomic: false
- implement: true

##### 1.5.1.3
To reach technical interoperability it is necessary not only that telegrams are generated and understood according to well specified rules but also that a train respectively trackside equipment reacts in a uniform way to information received. Technical interoperability requires specifications of a detailed level.
- kind: ordinary
- implementerEnhanced: To reach technical interoperability it is necessary not only that telegrams are generated and understood according to well specified rules but also that a train respectively
  trackside
  [EXTERNAL]
  equipment reacts in a uniform way to information received. Technical interoperability requires specifications of a detailed level.
- Legal Obligation: unknown
- WordTraceId: 4726
- atomic: false
- implement: true

##### 1.5.1.4
For operational interoperability it is necessary to add operating rules, engineering standards etc. to the system design. Reaching operational interoperability is outside the scope of the SRS.
- kind: ordinary
- implementerEnhanced: For operational interoperability it is necessary to add operating rules, engineering standards
  etc.
  [WEAK]
  to the system design. Reaching operational interoperability is outside the scope of the SRS.
- Legal Obligation: unknown
- WordTraceId: 5042
- atomic: false
- implement: true

### 1.6
How to Read and Use the SRS
- kind: Heading
- Legal Obligation: not applicable
- WordTraceId: 5236
- atomic: false
- implement: false

#### 1.6.1
PLACEHOLDER REQUIREMENT - DO NOT TRACE
- kind: Placeholder
- Legal Obligation: not applicable
- WordTraceId: 5265
- atomic: false
- implement: false

##### 1.6.1.1
The SRS covers 8 chapters, which are briefly described in the section following this introduction.
- kind: ordinary
- Legal Obligation: unknown
- WordTraceId: 5265
- atomic: true
- implement: true

##### 1.6.1.2
All readers may need to refer to the Glossary of terms and abbreviations (SUBSET-023).
- kind: ordinary
- Legal Obligation: optional
- WordTraceId: 5364
- atomic: true
- implement: true

### 1.7
Mandatory and Optional Requirements
- kind: Heading
- Legal Obligation: not applicable
- WordTraceId: 5451
- atomic: false
- implement: false

#### 1.7.1
PLACEHOLDER REQUIREMENT - DO NOT TRACE
- kind: Placeholder
- Legal Obligation: not applicable
- WordTraceId: 5488
- atomic: false
- implement: false

##### 1.7.1.1
This specification often offers multiple solutions on how to implement a specific function. It therefore contains both mandatory and optional requirements. Mandatory requirements are always referred to using the word “shall” where else optional requirements are referred to using the word “may”.
- kind: ordinary
- Legal Obligation: unknown
- WordTraceId: 5488
- atomic: false
- implement: true

##### 1.7.1.2
The ERTMS/ETCS on-board equipment shall implement all mandatory requirements, with the only exceptions and conditions explicitly stated in the Control-Command and Signalling TSI and in this SRS.
- kind: ordinary
- implementerEnhanced: The
  ERTMS/ETCS on-board equipment
  [SELF]
  shall implement all mandatory requirements, with the only exceptions and conditions explicitly stated in the Control-Command and Signalling TSI and in this SRS.
- Legal Obligation: mandatory
- WordTraceId: 5785
- atomic: true
- implement: true

##### 1.7.1.3
For ERTMS/ETCS trackside the implementation of functions has to be defined according to the characteristics of the specific lines and the related operational needs. In any case, the requirements of this SRS related to the implemented functions shall be respected.
- kind: ordinary
- implementerEnhanced: For ERTMS/ETCS
  trackside
  [EXTERNAL]
  the implementation of functions has to be defined according to the characteristics of the specific lines and the related operational needs. In any case, the requirements of this SRS related to the implemented functions shall be respected.
- Legal Obligation: mandatory
- WordTraceId: 5980
- atomic: false
- implement: true

##### 1.7.1.4
Notes are added to the specification in some parts for clarification. They however never contain requirements.
- kind: ordinary
- Legal Obligation: unknown
- WordTraceId: 6244
- atomic: false
- implement: true

##### 1.7.1.5
Not specified requirements and solutions are only permitted as long as they do not generate any interoperability problems.
- kind: ordinary
- implementerEnhanced: Not specified requirements and solutions are only permitted
  as long as
  [TIME]
  they do not generate any interoperability problems.
- Legal Obligation: unknown
- WordTraceId: 6355
- atomic: true
- implement: true

### 1.8
Contents of the SRS
- kind: Heading
- Legal Obligation: not applicable
- WordTraceId: 6481
- atomic: false
- implement: false

#### 1.8.1
PLACEHOLDER REQUIREMENT - DO NOT TRACE
- kind: Placeholder
- Legal Obligation: not applicable
- WordTraceId: 6501
- atomic: false
- implement: false

##### 1.8.1.1
The SRS defines the system requirements for the European Train Control System (ETCS) of ERTMS..
- kind: Definition
- Legal Obligation: unknown
- WordTraceId: 6501
- atomic: true
- implement: false

##### 1.8.1.2
This sub-section is intended to give a rough overview of the contents of each chapter within the SRS so that readers interested only in specialised subjects can easily find the relevant chapters.
- kind: ordinary
- implementerEnhanced: This sub-section is intended to give a
  rough
  [WEAK]
  overview of the contents of each chapter within the SRS so that readers interested only in specialised subjects can easily find the relevant chapters.
- Legal Obligation: unknown
- WordTraceId: 6598
- atomic: true
- implement: true

#### 1.8.2
Chapter 1: Introduction
- kind: Heading
- Legal Obligation: not applicable
- WordTraceId: 6794
- atomic: false
- implement: false

##### 1.8.2.1
Chapter 1 (this chapter) gives a general introduction to the intention and structure of the SRS, including a brief overview of the contents of each chapter.
- kind: ordinary
- Legal Obligation: unknown
- WordTraceId: 6818
- atomic: true
- implement: true

#### 1.8.3
Chapter 2: Basic System Description
- kind: Heading
- Legal Obligation: not applicable
- WordTraceId: 6975
- atomic: false
- implement: false

##### 1.8.3.1
Chapter 2 gives an overview of the ERTMS/ETCS system structure.
- kind: ordinary
- Legal Obligation: unknown
- WordTraceId: 7011
- atomic: true
- implement: true

##### 1.8.3.2
Chapter 2 also contains a description of the basic application levels.
- kind: ordinary
- Legal Obligation: unknown
- WordTraceId: 7075
- atomic: true
- implement: true

##### 1.8.3.3
Chapter 2 does not contain technical requirements.
- kind: ordinary
- Legal Obligation: unknown
- WordTraceId: 7147
- atomic: true
- implement: true

#### 1.8.4
Chapter 3: Principles
- kind: Heading
- Legal Obligation: not applicable
- WordTraceId: 7199
- atomic: false
- implement: false

##### 1.8.4.1
Chapter 3 specifies the system principles of ETCS/ERTMS. These principles apply to onboard and trackside subsystems.
- kind: ordinary
- implementerEnhanced: Chapter 3 specifies the system principles of ETCS/ERTMS. These principles apply to onboard and
  trackside
  [EXTERNAL]
  subsystems.
- Legal Obligation: unknown
- WordTraceId: 7221
- atomic: false
- implement: true

##### 1.8.4.2
The principles define the behaviour of the system in general and functional terms.
- kind: ordinary
- Legal Obligation: unknown
- WordTraceId: 7339
- atomic: true
- implement: true

#### 1.8.5
Chapter 4: Modes and Transitions
- kind: Heading
- Legal Obligation: not applicable
- WordTraceId: 7423
- atomic: false
- implement: false

##### 1.8.5.1
PLACEHOLDER REQUIREMENT - DO NOT TRACE
- kind: Placeholder
- Legal Obligation: not applicable
- WordTraceId: 7456
- atomic: false
- implement: false

###### 1.8.5.1.1
Chapter 4 defines the modes of the ERTMS/ETCS onboard equipment and all transitions between modes.
- kind: Definition
- implementerEnhanced: Chapter 4 defines the modes of the
  ERTMS/ETCS onboard equipment
  [SELF]
  and all transitions between modes.
- Legal Obligation: unknown
- WordTraceId: 7456
- atomic: true
- implement: false

#### 1.8.6
Chapter 5: Procedures
- kind: Heading
- Legal Obligation: not applicable
- WordTraceId: 7555
- atomic: false
- implement: false

##### 1.8.6.1
Chapter 5 defines the dynamic behaviour of procedures that are necessary for interoperability. Procedures are presented by a state transition chart and a corresponding table, where all elements (States, events, transitions) of the chart are defined. The description of the procedures shows all states of the ERTMS/ETCS onboard unit and the conditions that must be fulfilled to switch from one state to another.
- kind: Definition
- implementerEnhanced: Chapter 5 defines the dynamic behaviour of procedures that are necessary for interoperability. Procedures are presented by a state transition chart and a corresponding table, where all elements (States, events, transitions) of the chart are defined. The description of the procedures shows all states of the
  ERTMS/ETCS onboard
  [SELF]
  unit and the conditions that must be fulfilled to switch from one state to another.
- Legal Obligation: unknown
- WordTraceId: 7577
- atomic: false
- implement: false

#### 1.8.7
Chapter 6: Management of older System Versions
- kind: Heading
- Legal Obligation: not applicable
- WordTraceId: 7988
- atomic: false
- implement: false

##### 1.8.7.1
PLACEHOLDER REQUIREMENT - DO NOT TRACE
- kind: Placeholder
- Legal Obligation: not applicable
- WordTraceId: 8035
- atomic: false
- implement: false

###### 1.8.7.1.1
Chapter 6 defines the envelope of legally operated system versions and lists the exceptions that shall apply by derogation to the requirements listed in the other chapters of the SRS, when an older ERTMS/ETCS system version is used by the trackside subsystem.
- kind: Definition
- implementerEnhanced: Chapter 6 defines the envelope of legally operated system versions and lists the exceptions that shall apply by derogation to the requirements listed in the other chapters of the SRS,
  when
  [CONDITION]
  an older ERTMS/ETCS system version is used by the
  trackside
  [EXTERNAL]
  subsystem.
- Legal Obligation: mandatory
- WordTraceId: 8035
- atomic: true
- implement: false

#### 1.8.8
Chapter 7: ERTMS/ETCS Language
- kind: Heading
- Legal Obligation: not applicable
- WordTraceId: 8295
- atomic: false
- implement: false

##### 1.8.8.1
Chapter 7 defines and describes the necessary variables to be used for the data flow over the air gap between track and train. The grouping of these into packets is described. The format of messages is given in Chapter 8.
- kind: Definition
- Legal Obligation: unknown
- WordTraceId: 8326
- atomic: false
- implement: false

#### 1.8.9
Chapter 8: Messages
- kind: Heading
- Legal Obligation: not applicable
- WordTraceId: 8548
- atomic: false
- implement: false

##### 1.8.9.1
Chapter 8 defines the application protocol (format and content of messages, logical sequence for radio) necessary to achieve technical interoperability.
- kind: Definition
- Legal Obligation: unknown
- WordTraceId: 8568
- atomic: true
- implement: false

##### 1.8.9.2
The scope of this chapter is limited to the application protocol and the content of messages.
- kind: ordinary
- Legal Obligation: unknown
- WordTraceId: 8721
- atomic: true
- implement: true
